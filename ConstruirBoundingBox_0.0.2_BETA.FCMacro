import FreeCAD
import Sketcher

# Autor:			18Turbo
# Fecha:		13-08-2022
# Versión:		0.0.2 BETA
#	
# Funcionalidad:	Genera el BoundingBox de un sketch y lo traslada a otro sketch
#
# Descripción:	
#
#
# Notas de versiones:
# v.0.0.2 BETA:    Funcional en cualquier sketch para cualquier vista
# v.0.0.1 ALFA:    Funcional solo para sketch en planta, a la espera de reporte de errores
#



#Comprobar sketch seleccionado
objetosSeleccionados=Gui.Selection.getSelection()
if (len(objetosSeleccionados) == 1) and (objetosSeleccionados[0].Name.find('Sketch') > -1):

    #Crear Nuevo Sketch
    nombreBocetoOriginal = objetosSeleccionados[0].Name
    nombreBocetoBB = objetosSeleccionados[0].Label + "(BoundBox)"
    f = App.activeDocument().addObject('Sketcher::SketchObject', nombreBocetoBB
    f.Placement.Rotation = App.ActiveDocument.getObject(nombreBocetoOriginal).Placement.Rotation
    App.activeDocument().Sketch.MapMode = "Deactivated"
    xmin = App.ActiveDocument.getObject(nombreBocetoOriginal).Shape.BoundBox.XMin
    xmax = App.ActiveDocument.getObject(nombreBocetoOriginal).Shape.BoundBox.XMax
    ymin = App.ActiveDocument.getObject(nombreBocetoOriginal).Shape.BoundBox.YMin
    ymax = App.ActiveDocument.getObject(nombreBocetoOriginal).Shape.BoundBox.YMax
    zmin = App.ActiveDocument.getObject(nombreBocetoOriginal).Shape.BoundBox.ZMin
    zmax = App.ActiveDocument.getObject(nombreBocetoOriginal).Shape.BoundBox.ZMax
    xlen = App.ActiveDocument.getObject(nombreBocetoOriginal).Shape.BoundBox.XLength
    ylen = App.ActiveDocument.getObject(nombreBocetoOriginal).Shape.BoundBox.YLength
    zlen = App.ActiveDocument.getObject(nombreBocetoOriginal).Shape.BoundBox.ZLength

    geoList = []

    if (round(ylen) == 0):
        ymin = zmin
        ymax = zmax
    elif (round(xlen) == 0):
        xmin = ymin
        xmax = ymax
        ymin = zmin
        ymax = zmax

    geoList.append(Part.LineSegment(App.Vector(xmin,ymax,0),App.Vector(xmax,ymax,0)))
    geoList.append(Part.LineSegment(App.Vector(xmax,ymax,0),App.Vector(xmax,ymin,0)))
    geoList.append(Part.LineSegment(App.Vector(xmax,ymin,0),App.Vector(xmin,ymin,0)))
    geoList.append(Part.LineSegment(App.Vector(xmin,ymin,0),App.Vector(xmin,ymax,0)))    

    f.addGeometry(geoList,False)
    conList = []
    conList.append(Sketcher.Constraint('Coincident',0,2,1,1))
    conList.append(Sketcher.Constraint('Coincident',1,2,2,1))
    conList.append(Sketcher.Constraint('Coincident',2,2,3,1))
    conList.append(Sketcher.Constraint('Coincident',3,2,0,1))
    conList.append(Sketcher.Constraint('Horizontal',0))
    conList.append(Sketcher.Constraint('Horizontal',2))
    conList.append(Sketcher.Constraint('Vertical',1))
    conList.append(Sketcher.Constraint('Vertical',3))
    f.addConstraint(conList)
    del geoList, conList

    App.ActiveDocument.recompute()
else:
    App.Console.PrintWarning("Debes seleccionar un boceto (sketch)")
